-- SPDX-License-Identifier: BSD-3-Clause
--
-- Copyright (C) 2009 IETF Trust and the persons identified as authors
-- of the code
--
-- https://www.rfc-editor.org/rfc/rfc5652#section-3

AA ::= 	CHOICE {
	aaSet		[0] IMPLICIT AASet,
	aaSequence	[2] EXPLICIT SEQUENCE OF AuthenticatedAttribute
}

AASet ::= SET OF AuthenticatedAttribute

AuthenticatedAttribute ::= SEQUENCE {
	type	OBJECT IDENTIFIER ({ pkcs7_aa_note_OID }),
	values	SET OF ANY ({ pkcs7_aa_note_attr })
}
